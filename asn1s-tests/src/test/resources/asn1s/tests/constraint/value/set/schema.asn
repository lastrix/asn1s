Constraint-Set-Module
DEFINITIONS AUTOMATIC TAGS ::=
BEGIN
EXPORTS ALL;
    My-Set ::= SEQUENCE {
        int INTEGER,
        int2 INTEGER OPTIONAL,
        double REAL OPTIONAL,
        string UTF8String OPTIONAL
    }
    Constrained-Set ::= My-Set ( {int 1, string 'Hello!'} | {int 2, string 'Welcome!'} )
END
