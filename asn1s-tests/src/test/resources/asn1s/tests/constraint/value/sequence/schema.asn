Constraint-Sequence-Module
DEFINITIONS AUTOMATIC TAGS ::=
BEGIN
EXPORTS ALL;
    My-Sequence ::= SEQUENCE {
        int INTEGER,
        int2 INTEGER OPTIONAL,
        double REAL OPTIONAL,
        string UTF8String OPTIONAL
    }
    Constrained-Sequence ::= My-Sequence ( {int 1, string 'Hello!'} | {int 2, string 'Welcome!'} )
END
