Constraint-Choice-Module
DEFINITIONS AUTOMATIC TAGS ::=
BEGIN
EXPORTS ALL;
    My-Choice ::= CHOICE {
        null NULL,
        int INTEGER,
        int2 INTEGER,
        double REAL,
        string UTF8String
    }
    Constrained-Choice ::= My-Choice ( int:1 | int2:10 | double:2.5 | double:11.5)
END
